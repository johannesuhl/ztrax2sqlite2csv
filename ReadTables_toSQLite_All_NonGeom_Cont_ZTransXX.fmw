FME workspace ReadTables_toSQLite_All_NonGeom_Cont_ZTransXX.fmw

Parameters:
- DestDataset_SQLITE3_5 = H:\ZTRAX_ALL\SQLITE\XX_ZTrans_cont_SQLite.db   # SQLite Database
- SourceDataset_CSV2 = H:\ZTRAX_ALL\CSV\cont\XX\ZTrans\BKManagedSpecific.txt   # Source CSV (Comma Separated Value) File(s)
- SourceDataset_CSV2_33 = H:\ZTRAX_ALL\CSV\cont\XX\ZTrans\BorrowerMailAddress.txt   # Source CSV (Comma Separated Value) File(s)
- SourceDataset_CSV2_21 = H:\ZTRAX_ALL\CSV\cont\XX\ZTrans\BorrowerName.txt   # Source CSV (Comma Separated Value) File(s)
- SourceDataset_CSV2_29 = H:\ZTRAX_ALL\CSV\cont\XX\ZTrans\BorrowerNameDescriptionCode.txt   # Source CSV (Comma Separated Value) File(s)
- SourceDataset_CSV2_37 = H:\ZTRAX_ALL\CSV\cont\XX\ZTrans\BuyerMailAddress.txt   # Source CSV (Comma Separated Value) File(s)
- SourceDataset_CSV2_23 = H:\ZTRAX_ALL\CSV\cont\XX\ZTrans\BuyerName.txt   # Source CSV (Comma Separated Value) File(s)
- SourceDataset_CSV2_27 = H:\ZTRAX_ALL\CSV\cont\XX\ZTrans\BuyerNameDescriptionCode.txt   # Source CSV (Comma Separated Value) File(s)
- SourceDataset_CSV2_31 = H:\ZTRAX_ALL\CSV\cont\XX\ZTrans\ForeclosureNameAddress.txt   # Source CSV (Comma Separated Value) File(s)
- SourceDataset_CSV2_35 = H:\ZTRAX_ALL\CSV\cont\XX\ZTrans\ForeclosureNODNOSDoc.txt   # Source CSV (Comma Separated Value) File(s)
- SourceDataset_CSV2_39 = H:\ZTRAX_ALL\CSV\cont\XX\ZTrans\ForeclosureOriginalLoan.txt   # Source CSV (Comma Separated Value) File(s)
- SourceDataset_CSV2_22 = H:\ZTRAX_ALL\CSV\cont\XX\ZTrans\HawaiiBorrowerNotes.txt   # Source CSV (Comma Separated Value) File(s)
- SourceDataset_CSV2_26 = H:\ZTRAX_ALL\CSV\cont\XX\ZTrans\Legacy.txt   # Source CSV (Comma Separated Value) File(s)
- SourceDataset_CSV2_28 = H:\ZTRAX_ALL\CSV\cont\XX\ZTrans\Main.txt   # Source CSV (Comma Separated Value) File(s)
- SourceDataset_CSV2_30 = H:\ZTRAX_ALL\CSV\cont\XX\ZTrans\Modification.txt   # Source CSV (Comma Separated Value) File(s)
- SourceDataset_CSV2_32 = H:\ZTRAX_ALL\CSV\cont\XX\ZTrans\RegionSpecific.txt   # Source CSV (Comma Separated Value) File(s)
- SourceDataset_CSV2_34 = H:\ZTRAX_ALL\CSV\cont\XX\ZTrans\SellerMailAddress.txt   # Source CSV (Comma Separated Value) File(s)
- SourceDataset_CSV2_36 = H:\ZTRAX_ALL\CSV\cont\XX\ZTrans\SellerName.txt   # Source CSV (Comma Separated Value) File(s)
- SourceDataset_CSV2_38 = H:\ZTRAX_ALL\CSV\cont\XX\ZTrans\SellerNameDescriptionCode.txt   # Source CSV (Comma Separated Value) File(s)
- SourceDataset_CSV2_25 = H:\ZTRAX_ALL\CSV\cont\XX\ZTrans\HawaiiGranteeNotes.txt   # Source CSV (Comma Separated Value) File(s)
- SourceDataset_CSV2_24 = ""H:\ZTRAX_ALL\CSV\cont\XX\ZTrans\BKManagedSpecific.txt" "H:\ZTRAX_ALL\CSV\cont\XX\ZTrans\BorrowerMailAddress.txt" "H:\ZTRAX_ALL\CSV\cont\XX\ZTrans\BorrowerName.txt" "H:\ZTRAX_ALL\CSV\cont\XX\ZTrans\BorrowerNameDescriptionCode.txt" "H:\ZTRAX_ALL\CSV\cont\XX\ZTrans\BuyerMailAddress.txt" "H:\ZTRAX_ALL\CSV\cont\XX\ZTrans\BuyerName.txt" "H:\ZTRAX_ALL\CSV\cont\XX\ZTrans\BuyerNameDescriptionCode.txt" "H:\ZTRAX_ALL\CSV\cont\XX\ZTrans\ForeclosureNameAddress.txt" "H:\ZTRAX_ALL\CSV\cont\XX\ZTrans\ForeclosureNODNOSDoc.txt" "H:\ZTRAX_ALL\CSV\cont\XX\ZTrans\ForeclosureOriginalLoan.txt" "H:\ZTRAX_ALL\CSV\cont\XX\ZTrans\HawaiiBorrowerNotes.txt" "H:\ZTRAX_ALL\CSV\cont\XX\ZTrans\HawaiiGranteeNotes.txt" "H:\ZTRAX_ALL\CSV\cont\XX\ZTrans\Legacy.txt" "H:\ZTRAX_ALL\CSV\cont\XX\ZTrans\Main.txt" "H:\ZTRAX_ALL\CSV\cont\XX\ZTrans\Modification.txt" "H:\ZTRAX_ALL\CSV\cont\XX\ZTrans\PropertyInfo.txt" "H:\ZTRAX_ALL\CSV\cont\XX\ZTrans\RegionSpecific.txt" "H:\ZTRAX_ALL\CSV\cont\XX\ZTrans\SellerMailAddress.txt" "H:\ZTRAX_ALL\CSV\cont\XX\ZTrans\SellerName.txt" "H:\ZTRAX_ALL\CSV\cont\XX\ZTrans\SellerNameDescriptionCode.txt""   # Source CSV (Comma Separated Value) File(s)

Readers:
- CSV2_1: CSV2 from $(SourceDataset_CSV2) in EPSG:4267
- CSV2_2: CSV2 from $(SourceDataset_CSV2_33) in EPSG:4267
- CSV2_3: CSV2 from $(SourceDataset_CSV2_21) in EPSG:4267
- CSV2_4: CSV2 from $(SourceDataset_CSV2_29) in EPSG:4267
- CSV2_5: CSV2 from $(SourceDataset_CSV2_37) in EPSG:4267
- CSV2_6: CSV2 from $(SourceDataset_CSV2_23) in EPSG:4267
- CSV2_7: CSV2 from $(SourceDataset_CSV2_27) in EPSG:4267
- CSV2_8: CSV2 from $(SourceDataset_CSV2_31) in EPSG:4267
- CSV2_9: CSV2 from $(SourceDataset_CSV2_35) in EPSG:4267
- CSV2_10: CSV2 from $(SourceDataset_CSV2_39) in EPSG:4267
- CSV2_11: CSV2 from $(SourceDataset_CSV2_22) in EPSG:4267
- CSV2_12: CSV2 from $(SourceDataset_CSV2_26) in EPSG:4267
- CSV2_13: CSV2 from $(SourceDataset_CSV2_28) in EPSG:4267
- CSV2_14: CSV2 from $(SourceDataset_CSV2_30) in EPSG:4267
- CSV2_15: CSV2 from $(SourceDataset_CSV2_32) in EPSG:4267
- CSV2_16: CSV2 from $(SourceDataset_CSV2_34) in EPSG:4267
- CSV2_17: CSV2 from $(SourceDataset_CSV2_36) in EPSG:4267
- CSV2_18: CSV2 from $(SourceDataset_CSV2_38) in EPSG:4267
- CSV2_19: CSV2 from $(SourceDataset_CSV2_25) in EPSG:4267
- CSV2_20: CSV2 from $(SourceDataset_CSV2_24)

Writers:
- SQLITE3_1: SQLITE3 to $(DestDataset_SQLITE3_5)

PropertyInfo (reader CSV2_20)
    attributes: TransId string, AssessorParcelNumber string, APNIndicatorStndCode string, TaxIDNumber string, TaxIDIndicatorStndCode string, UnformattedAssessorParcelNumber string, AlternateParcelNumber string, HawaiiCondoCPRCode string, PropertyHouseNumber string, PropertyHouseNumberExt string, PropertyStreetPreDirectional string, PropertyStreetName string, PropertyStreetSuffix string, PropertyStreetPostDirectional string, PropertyBuildingNumber string, PropertyFullStreetAddress string, PropertyCity string, PropertyState string, PropertyZip string, PropertyZip4 string, OriginalPropertyFullStreetAddress string, OriginalPropertyAddressLastline string, PropertyAddressStndCode string, LegalLot string, LegalOtherLot string, LegalLotCode string, LegalBlock string, LegalSubdivisionName string, LegalCondoProjectPUDDevName string, LegalBuildingNumber string,
      LegalUnit string, LegalSection string, LegalPhase string, LegalTract string, LegalDistrict string, LegalMunicipality string, LegalCity string, LegalTownship string, LegalSTRSection string, LegalSTRTownship string, LegalSTRRange string, LegalSTRMeridian string, LegalSecTwnRngMer string, LegalRecordersMapReference string, LegalDescription string, LegalLotSize string, PropertySequenceNumber string, PropertyAddressMatchcode string, PropertyAddressUnitDesignator string, PropertyAddressUnitNumber string, PropertyAddressCarrierRoute string, PropertyAddressGeoCodeMatchCode string, PropertyAddressLatitude string, PropertyAddressLongitude string, PropertyAddressCensusTractAndBlock string, PropertyAddressConfidenceScore string, PropertyAddressCBSACode string, PropertyAddressCBSADivisionCode string, PropertyAddressMatchType string, PropertyAddressDPV string,
      PropertyGeocodeQualityCode string, PropertyAddressQualityCode string, FIPS string, LoadID string, ImportParcelID string, BKFSPID string, AssessmentRecordMatchFlag string, BatchID string
    -> Counter_21
Counter_21
    CNT_ATTR = fme_id
    DOMAIN = counter
    SCOPE = Local
    START = 1
    -> cont_ztrans_utproperty (writer SQLITE3_1)
    <REJECTED> -> cont_ztrans_utproperty (writer SQLITE3_1)
cont_ztrans_utproperty (writer SQLITE3_1)
    attributes: TransId integer, SellerMailSequenceNumber integer, SellerMailAddressStndCode text, SellerMailCareOfName text, SellerMailHouseNumber text, SellerMailHouseNumberExt text, SellerMailStreetPreDirectional text, SellerMailStreetName text, SellerMailStreetSuffix text, SellerMailStreetPostDirectional text, SellerMailBuildingName text, SellerMailBuildingNumber text, SellerMailFullStreetAddress text, SellerMailCity text, SellerMailState text, SellerMailZip text, SellerMailZip4 text, OriginalSellerMailFullStreetAddress text, OriginalSellerMailAddressLastline text, SellerMailAddressMatchCode text, SellerMailAddressUnitDesignatorCode text, SellerMailAddressUnitNumber text, SellerMailAddressCarrierRoute text, SellerMailAddressFIPSCode text, SellerMailAddressLatitude float, SellerMailAddressLongitude float, SellerMailAddressCensusTractAndBlock text, SellerMailAddressConfidenceScore integer, SellerMailAddressCBSACode integer, SellerMailAddressCBSADivisionCode integer,
      SellerMailAddressMatchType integer, SellerMailAddressDPV text, SellerMailAddressGeocodeQualityCode text, SellerMailAddressQualityCode text, LoadID integer, FIPS text, BatchID integer, fme_id integer
HawaiiGranteeNotes (reader CSV2_19)
    attributes: TransID string, GranteeNotesSequenceNumber string, HawaiiGranteeNotesStndCode string, HawaiiGranteeNotes string, LoadID string, GranteeNameSequenceNumber string, FIPS string, BatchID string
    -> Counter_20
Counter_20
    CNT_ATTR = fme_id
    DOMAIN = counter
    SCOPE = Local
    START = 1
    -> cont_ztrans_uthawaiigranteenotes (writer SQLITE3_1)
    <REJECTED> -> cont_ztrans_uthawaiigranteenotes (writer SQLITE3_1)
cont_ztrans_uthawaiigranteenotes (writer SQLITE3_1)
    attributes: TransID integer, GranteeNotesSequenceNumber integer, HawaiiGranteeNotesStndCode text, HawaiiGranteeNotes text, LoadID integer, GranteeNameSequenceNumber integer, FIPS text, BatchID integer, fme_id integer

Bookmark: cont_ztrans
HawaiiBorrowerNotes (reader CSV2_11)
    attributes: TransID string, BorrowerNotesSequenceNumber string, HawaiiBorrowerNotesStndCode string, HawaiiBorrowerNotes string, LoadID string, BorrowerNameSequenceNumber string, FIPS string, BatchID string
    -> Counter_11
Counter_11
    CNT_ATTR = fme_id
    DOMAIN = counter
    SCOPE = Local
    START = 1
    -> cont_ztrans_uthawaiiborrowernotes (writer SQLITE3_1)
    <REJECTED> -> cont_ztrans_uthawaiiborrowernotes (writer SQLITE3_1)
cont_ztrans_uthawaiiborrowernotes (writer SQLITE3_1)
    attributes: TransID integer, BorrowerNotesSequenceNumber integer, HawaiiBorrowerNotesStndCode text, HawaiiBorrowerNotes text, LoadID integer, BorrowerNameSequenceNumber integer, FIPS text, BatchID integer, fme_id integer
BorrowerMailAddress (reader CSV2_2)
    attributes: TransId string, BorrowerMailSequenceNumber string, BorrowerMailCareOfName string, BorrowerMailHouseNumber string, BorrowerMailHouseNumberExt string, BorrowerMailStreetPreDirectional string, BorrowerMailStreetName string, BorrowerMailStreetSuffix string, BorrowerMailStreetPostDirectional string, BorrowerMailBuildingName string, BorrowerMailBuildingNumber string, BorrowerMailFullStreetAddress string, BorrowerMailCity string, BorrowerMailState string, BorrowerMailZip string, BorrowerMailZip4 string, OriginalBorrowerMailFullStreetAddress string, OriginalBorrowerMailAddressLastline string, BorrowerMailAddressStndCode string, BorrowerMailAddressMatchCode string, BorrowerMailAddressUnitDesignatorCode string, BorrowerMailAddressUnitNumber string, BorrowerMailAddressCarrierRoute string, BorrowerMailAddressFIPSCode string, BorrowerMailAddressLatitude string, BorrowerMailAddressLongitude string, BorrowerMailAddressCensusTractAndBlock string, BorrowerMailAddressConfidenceScore string, BorrowerMailAddressCBSACode string, BorrowerMailAddressCBSADivisionCode string,
      BorrowerMailAddressMatchType string, BorrowerMailAddressDPV string, BorrowerMailAddressGeocodeQualityCode string, BorrowerMailAddressQualityCode string, LoadID string, FIPS string, BatchID string
    -> Counter_3
Counter_3
    CNT_ATTR = fme_id
    DOMAIN = counter
    SCOPE = Local
    START = 1
    -> cont_ztrans_utborrowermailaddress (writer SQLITE3_1)
    <REJECTED> -> cont_ztrans_utborrowermailaddress (writer SQLITE3_1)
cont_ztrans_utborrowermailaddress (writer SQLITE3_1)
    attributes: TransId integer, BorrowerMailSequenceNumber integer, BorrowerMailCareOfName text, BorrowerMailHouseNumber text, BorrowerMailHouseNumberExt text, BorrowerMailStreetPreDirectional text, BorrowerMailStreetName text, BorrowerMailStreetSuffix text, BorrowerMailStreetPostDirectional text, BorrowerMailBuildingName text, BorrowerMailBuildingNumber text, BorrowerMailFullStreetAddress text, BorrowerMailCity text, BorrowerMailState text, BorrowerMailZip text, BorrowerMailZip4 text, OriginalBorrowerMailFullStreetAddress text, OriginalBorrowerMailAddressLastline text, BorrowerMailAddressStndCode text, BorrowerMailAddressMatchCode text, BorrowerMailAddressUnitDesignatorCode text, BorrowerMailAddressUnitNumber text, BorrowerMailAddressCarrierRoute text, BorrowerMailAddressFIPSCode text, BorrowerMailAddressLatitude float, BorrowerMailAddressLongitude float, BorrowerMailAddressCensusTractAndBlock text, BorrowerMailAddressConfidenceScore integer, BorrowerMailAddressCBSACode integer, BorrowerMailAddressCBSADivisionCode integer,
      BorrowerMailAddressMatchType integer, BorrowerMailAddressDPV text, BorrowerMailAddressGeocodeQualityCode text, BorrowerMailAddressQualityCode text, LoadID integer, FIPS text, BatchID integer, fme_id integer
BuyerName (reader CSV2_6)
    attributes: TransId string, BuyerFirstMiddleName string, BuyerLastName string, BuyerIndividualFullName string, BuyerNonIndividualName string, BuyerNameSequenceNumber string, BuyerMailSequenceNumber string, LoadID string, FIPS string, BatchID string
    -> Counter_7
Counter_7
    CNT_ATTR = fme_id
    DOMAIN = counter
    SCOPE = Local
    START = 1
    -> cont_ztrans_utbuyername (writer SQLITE3_1)
    <REJECTED> -> cont_ztrans_utbuyername (writer SQLITE3_1)
cont_ztrans_utbuyername (writer SQLITE3_1)
    attributes: TransId integer, BuyerFirstMiddleName text, BuyerLastName text, BuyerIndividualFullName text, BuyerNonIndividualName text, BuyerNameSequenceNumber integer, BuyerMailSequenceNumber integer, LoadID integer, FIPS text, BatchID integer, fme_id integer
SellerNameDescriptionCode (reader CSV2_18)
    attributes: TransId string, SellerDescriptionStndCode string, SellerDescSequenceNumber string, SellerNameSequenceNumber string, FIPS string, BatchID string
    -> Counter_9
Counter_9
    CNT_ATTR = fme_id
    DOMAIN = counter
    SCOPE = Local
    START = 1
    -> cont_ztrans_utsellernamedescriptioncode (writer SQLITE3_1)
    <REJECTED> -> cont_ztrans_utsellernamedescriptioncode (writer SQLITE3_1)
cont_ztrans_utsellernamedescriptioncode (writer SQLITE3_1)
    attributes: TransId integer, SellerDescriptionStndCode text, SellerDescSequenceNumber integer, SellerNameSequenceNumber integer, FIPS text, BatchID integer, fme_id integer
BuyerNameDescriptionCode (reader CSV2_7)
    attributes: TransId string, BuyerDescriptionStndCode string, BuyerDescSequenceNumber string, BuyerNameSequenceNumber string, FIPS string, BatchID string
    -> Counter_4
Counter_4
    CNT_ATTR = fme_id
    DOMAIN = counter
    SCOPE = Local
    START = 1
    -> cont_ztrans_utbuyernamedescriptioncode (writer SQLITE3_1)
    <REJECTED> -> cont_ztrans_utbuyernamedescriptioncode (writer SQLITE3_1)
cont_ztrans_utbuyernamedescriptioncode (writer SQLITE3_1)
    attributes: TransId integer, BuyerDescriptionStndCode text, BuyerDescSequenceNumber integer, BuyerNameSequenceNumber integer, FIPS text, BatchID integer, fme_id integer
BKManagedSpecific (reader CSV2_1)
    attributes: TransID string, Loan1TransType string, Loan2TransType string, DeedTransType string, BKFSPID string, FIPS string, BatchID string
    -> Counter_13
Counter_13
    CNT_ATTR = fme_id
    DOMAIN = counter
    SCOPE = Local
    START = 1
    -> cont_ztrans_utbkmanagedspecific (writer SQLITE3_1)
    <REJECTED> -> cont_ztrans_utbkmanagedspecific (writer SQLITE3_1)
cont_ztrans_utbkmanagedspecific (writer SQLITE3_1)
    attributes: TransID integer, Loan1TransType text, Loan2TransType text, DeedTransType text, BKFSPID integer, FIPS text, BatchID integer, fme_id integer
RegionSpecific (reader CSV2_15)
    attributes: TransID string, RecordingDistrict string, DualSystemRecordingStndCode string, DualSystemRecordingDate string, DualSystemDocumentNumber string, DualSystemBookNumber string, DualSystemPageNumber string, HawaiiPreviousDualSystemRecStndCode string, HawaiiPreviousDualSystemDocNumber string, TransferCertificateofTitleNumber string, HawaiiTransferTaxRate string, LegalHawaiiLandCourtAppNo string, LegalHawaiiLandCourtMapNo string, LegalHawaiiLandCourtConsolidationNo string, LegalHawaiiRegularSystemFilePlanNo string, SaleResultsOrStatusStndCode string, LoadID string, FIPS string, BatchID string
    -> Counter_16
Counter_16
    CNT_ATTR = fme_id
    DOMAIN = counter
    SCOPE = Local
    START = 1
    -> cont_ztrans_utregionspecific (writer SQLITE3_1)
    <REJECTED> -> cont_ztrans_utregionspecific (writer SQLITE3_1)
cont_ztrans_utregionspecific (writer SQLITE3_1)
    attributes: TransID integer, RecordingDistrict text, DualSystemRecordingStndCode text, DualSystemRecordingDate text, DualSystemDocumentNumber text, DualSystemBookNumber text, DualSystemPageNumber text, HawaiiPreviousDualSystemRecStndCode text, HawaiiPreviousDualSystemDocNumber text, TransferCertificateofTitleNumber text, HawaiiTransferTaxRate text, LegalHawaiiLandCourtAppNo text, LegalHawaiiLandCourtMapNo text, LegalHawaiiLandCourtConsolidationNo text, LegalHawaiiRegularSystemFilePlanNo text, SaleResultsOrStatusStndCode text, LoadID integer, FIPS text, BatchID integer, fme_id integer
BorrowerName (reader CSV2_3)
    attributes: TransId string, BorrowerFirstMiddleName string, BorrowerLastName string, BorrowerIndividualFullName string, BorrowerNonIndividualName string, BorrowerNameSequenceNumber string, BorrowerMailSequenceNumber string, LoadID string, FIPS string, BatchID string
    -> Counter_5
Counter_5
    CNT_ATTR = fme_id
    DOMAIN = counter
    SCOPE = Local
    START = 1
    -> cont_ztrans_utborrowername (writer SQLITE3_1)
    <REJECTED> -> cont_ztrans_utborrowername (writer SQLITE3_1)
cont_ztrans_utborrowername (writer SQLITE3_1)
    attributes: TransId integer, BorrowerFirstMiddleName text, BorrowerLastName text, BorrowerIndividualFullName text, BorrowerNonIndividualName text, BorrowerNameSequenceNumber integer, BorrowerMailSequenceNumber integer, LoadID integer, FIPS text, BatchID integer, fme_id integer
BorrowerNameDescriptionCode (reader CSV2_4)
    attributes: TransId string, BorrowerDescriptionStndCode string, BorrowerDescSequenceNumber string, BorrowerNameSequenceNumber string, FIPS string, BatchID string
    -> Counter_18
Counter_18
    CNT_ATTR = fme_id
    DOMAIN = counter
    SCOPE = Local
    START = 1
    -> cont_ztrans_utborrowernamedescriptioncode (writer SQLITE3_1)
    <REJECTED> -> cont_ztrans_utborrowernamedescriptioncode (writer SQLITE3_1)
cont_ztrans_utborrowernamedescriptioncode (writer SQLITE3_1)
    attributes: TransId integer, BorrowerDescriptionStndCode text, BorrowerDescSequenceNumber integer, BorrowerNameSequenceNumber integer, FIPS text, BatchID integer, fme_id integer
Modification (reader CSV2_14)
    attributes: TransId string, ModLoanSequenceNumber string, OrigLoanRecordingDate string, LastModRecordingDate string, OrigLoanDocumentDate string, LastModDocumentDate string, OrigLoanORLastModDocumentNumber string, OrigLoanORLastModBookNumber string, OrigLoanORLastModPageNumber string, OrigLoanORLastModLoanAmount string, LoadID string, FIPS string, BatchID string
    -> Counter_8
Counter_8
    CNT_ATTR = fme_id
    DOMAIN = counter
    SCOPE = Local
    START = 1
    -> cont_ztrans_utmodification (writer SQLITE3_1)
    <REJECTED> -> cont_ztrans_utmodification (writer SQLITE3_1)
cont_ztrans_utmodification (writer SQLITE3_1)
    attributes: TransId integer, ModLoanSequenceNumber integer, OrigLoanRecordingDate text, LastModRecordingDate text, OrigLoanDocumentDate text, LastModDocumentDate text, OrigLoanORLastModDocumentNumber text, OrigLoanORLastModBookNumber text, OrigLoanORLastModPageNumber text, OrigLoanORLastModLoanAmount float, LoadID integer, FIPS text, BatchID integer, fme_id integer
ForeclosureNODNOSDoc (reader CSV2_9)
    attributes: TransId string, OrigNODNOSRecSequenceNumber string, OrigNODNOSRecordingDate string, OrigNODNOSDocumentDate string, OrigNODNOSDocumentNumber string, OrigNODNOSBookNumber string, OrigNODNOSPageNumber string, LoadID string, FIPS string, BatchID string
    -> Counter_19
Counter_19
    CNT_ATTR = fme_id
    DOMAIN = counter
    SCOPE = Local
    START = 1
    -> cont_ztrans_utforeclosurenodnosdoc (writer SQLITE3_1)
    <REJECTED> -> cont_ztrans_utforeclosurenodnosdoc (writer SQLITE3_1)
cont_ztrans_utforeclosurenodnosdoc (writer SQLITE3_1)
    attributes: TransId integer, OrigNODNOSRecSequenceNumber integer, OrigNODNOSRecordingDate text, OrigNODNOSDocumentDate text, OrigNODNOSDocumentNumber text, OrigNODNOSBookNumber text, OrigNODNOSPageNumber text, LoadID integer, FIPS text, BatchID integer, fme_id integer
ForeclosureNameAddress (reader CSV2_8)
    attributes: TransId string, FCNameAddressSequenceNumber string, FCMailFirstMiddleName string, FCMailLastName string, FCMailIndividualFullName string, FCMailNonIndividualName string, FCMailCareOf string, FCMailFullStreetAddress string, FCMailBuildingName string, FCMailBuildingNumber string, FCMailUnitDesignator string, FCMailUnit string, FCMailCity string, FCMailState string, FCMailZip string, FCMailZip4 string, FCTelephoneNumber string, FCNameAddressStndCode string, LoadID string, FIPS string, BatchID string
    -> Counter_17
Counter_17
    CNT_ATTR = fme_id
    DOMAIN = counter
    SCOPE = Local
    START = 1
    -> cont_ztrans_utforeclosurenameaddress (writer SQLITE3_1)
    <REJECTED> -> cont_ztrans_utforeclosurenameaddress (writer SQLITE3_1)
cont_ztrans_utforeclosurenameaddress (writer SQLITE3_1)
    attributes: TransId integer, FCNameAddressSequenceNumber integer, FCMailFirstMiddleName text, FCMailLastName text, FCMailIndividualFullName text, FCMailNonIndividualName text, FCMailCareOf text, FCMailFullStreetAddress text, FCMailBuildingName text, FCMailBuildingNumber text, FCMailUnitDesignator text, FCMailUnit text, FCMailCity text, FCMailState text, FCMailZip text, FCMailZip4 text, FCTelephoneNumber text, FCNameAddressStndCode text, LoadID integer, FIPS text, BatchID integer, fme_id integer
Legacy (reader CSV2_12)
    attributes: TransID string, SecondMtgLoanAmount string, SecondMtgeLenderTypeStndCode string, WAExciseTaxNumber string, TNPreviousDocumentNumber string, TNPreviousPageNumber string, LoadID string, FIPS string, BatchID string
    -> Counter_10
Counter_10
    CNT_ATTR = fme_id
    DOMAIN = counter
    SCOPE = Local
    START = 1
    -> cont_ztrans_utlegacy (writer SQLITE3_1)
    <REJECTED> -> cont_ztrans_utlegacy (writer SQLITE3_1)
cont_ztrans_utlegacy (writer SQLITE3_1)
    attributes: TransID integer, SecondMtgLoanAmount float, SecondMtgeLenderTypeStndCode text, WAExciseTaxNumber text, TNPreviousDocumentNumber text, TNPreviousPageNumber text, LoadID integer, FIPS text, BatchID integer, fme_id integer
Main (reader CSV2_13)
    attributes: TransId string, FIPS string, State string, County string, DataClassStndCode string, RecordTypeStndCode string, RecordingDate string, RecordingDocumentNumber string, RecordingBookNumber string, RecordingPageNumber string, ReRecordedCorrectionStndCode string, PriorRecordingDate string, PriorDocumentDate string, PriorDocumentNumber string, PriorBookNumber string, PriorPageNumber string, DocumentTypeStndCode string, DocumentDate string, SignatureDate string, EffectiveDate string, BuyerVestingStndCode string, BuyerMultiVestingFlag string, PartialInterestTransferStndCode string, PartialInterestTransferPercent string, SalesPriceAmount string, SalesPriceAmountStndCode string, CityTransferTax string, CountyTransferTax string, StateTransferTax string, TotalTransferTax string,
      IntraFamilyTransferFlag string, TransferTaxExemptFlag string, PropertyUseStndCode string, AssessmentLandUseStndCode string, OccupancyStatusStndCode string, LegalStndCode string, BorrowerVestingStndCode string, LenderName string, LenderTypeStndCode string, LenderIDStndCode string, LenderDBAName string, DBALenderTypeStndCode string, DBALenderIDStndCode string, LenderMailCareOfName string, LenderMailHouseNumber string, LenderMailHouseNumberExt string, LenderMailStreetPreDirectional string, LenderMailStreetName string, LenderMailStreetSuffix string, LenderMailStreetPostDirectional string, LenderMailFullStreetAddress string, LenderMailBuildingName string, LenderMailBuildingNumber string, LenderMailUnitDesignator string, LenderMailUnit string, LenderMailCity string, LenderMailState string, LenderMailZip string, LenderMailZip4 string, LoanAmount string,
      LoanAmountStndCode string, MaximumLoanAmount string, LoanTypeStndCode string, LoanTypeClosedOpenEndStndCode string, LoanTypeFutureAdvanceFlag string, LoanTypeProgramStndCode string, LoanRateTypeStndCode string, LoanDueDate string, LoanTermMonths string, LoanTermYears string, InitialInterestRate string, ARMFirstAdjustmentDate string, ARMFirstAdjustmentMaxRate string, ARMFirstAdjustmentMinRate string, ARMIndexStndCode string, ARMAdjustmentFrequencyStndCode string, ARMMargin string, ARMInitialCap string, ARMPeriodicCap string, ARMLifetimeCap string, ARMMaxInterestRate string, ARMMinInterestRate string, InterestOnlyFlag string, InterestOnlyTerm string, PrepaymentPenaltyFlag string, PrepaymentPenaltyTerm string, BiWeeklyPaymentFlag string, AssumabilityRiderFlag string, BalloonRiderFlag string, CondominiumRiderFlag string,
      PlannedUnitDevelopmentRiderFlag string, SecondHomeRiderFlag string, OneToFourFamilyRiderFlag string, ConcurrentMtgeDocOrBkPg string, LoanNumber string, MERSMINNumber string, CaseNumber string, MERSFlag string, TitleCompanyName string, TitleCompanyIDStndCode string, AccommodationRecordingFlag string, UnpaidBalance string, InstallmentAmount string, InstallmentDueDate string, TotalDelinquentAmount string, DelinquentAsOfDate string, CurrentLender string, CurrentLenderTypeStndCode string, CurrentLenderIDStndCode string, TrusteeSaleNumber string, AttorneyFileNumber string, AuctionDate string, AuctionTime string, AuctionFullStreetAddress string, AuctionCityName string, StartingBid string, KeyedDate string, KeyerID string, SubVendorStndCode string, ImageFileName string,
      BuilderFlag string, MatchStndCode string, REOStndCode string, UpdateOwnershipFlag string, LoadID string, StatusInd string, TransactionTypeStndCode string, BatchID string, BKFSPID string, ZVendorStndCode string, SourceChkSum string
    -> Counter_14
Counter_14
    CNT_ATTR = fme_id
    DOMAIN = counter
    SCOPE = Local
    START = 1
    -> cont_ztrans_utmain (writer SQLITE3_1)
    <REJECTED> -> cont_ztrans_utmain (writer SQLITE3_1)
cont_ztrans_utmain (writer SQLITE3_1)
    attributes: TransId integer, FIPS text, State text, County text, DataClassStndCode text, RecordTypeStndCode text, RecordingDate text, RecordingDocumentNumber text, RecordingBookNumber text, RecordingPageNumber text, ReRecordedCorrectionStndCode text, PriorRecordingDate text, PriorDocumentDate text, PriorDocumentNumber text, PriorBookNumber text, PriorPageNumber text, DocumentTypeStndCode text, DocumentDate text, SignatureDate text, EffectiveDate text, BuyerVestingStndCode text, BuyerMultiVestingFlag text, PartialInterestTransferStndCode text, PartialInterestTransferPercent float, SalesPriceAmount float, SalesPriceAmountStndCode text, CityTransferTax float, CountyTransferTax float, StateTransferTax float, TotalTransferTax float,
      IntraFamilyTransferFlag text, TransferTaxExemptFlag text, PropertyUseStndCode text, AssessmentLandUseStndCode text, OccupancyStatusStndCode text, LegalStndCode text, BorrowerVestingStndCode text, LenderName text, LenderTypeStndCode text, LenderIDStndCode text, LenderDBAName text, DBALenderTypeStndCode text, DBALenderIDStndCode text, LenderMailCareOfName text, LenderMailHouseNumber text, LenderMailHouseNumberExt text, LenderMailStreetPreDirectional text, LenderMailStreetName text, LenderMailStreetSuffix text, LenderMailStreetPostDirectional text, LenderMailFullStreetAddress text, LenderMailBuildingName text, LenderMailBuildingNumber text, LenderMailUnitDesignator text, LenderMailUnit text, LenderMailCity text, LenderMailState text, LenderMailZip text, LenderMailZip4 text, LoanAmount float,
      LoanAmountStndCode text, MaximumLoanAmount float, LoanTypeStndCode text, LoanTypeClosedOpenEndStndCode text, LoanTypeFutureAdvanceFlag text, LoanTypeProgramStndCode text, LoanRateTypeStndCode text, LoanDueDate text, LoanTermMonths integer, LoanTermYears integer, InitialInterestRate float, ARMFirstAdjustmentDate text, ARMFirstAdjustmentMaxRate float, ARMFirstAdjustmentMinRate float, ARMIndexStndCode text, ARMAdjustmentFrequencyStndCode text, ARMMargin float, ARMInitialCap float, ARMPeriodicCap float, ARMLifetimeCap float, ARMMaxInterestRate float, ARMMinInterestRate float, InterestOnlyFlag text, InterestOnlyTerm text, PrepaymentPenaltyFlag text, PrepaymentPenaltyTerm text, BiWeeklyPaymentFlag text, AssumabilityRiderFlag text, BalloonRiderFlag text, CondominiumRiderFlag text,
      PlannedUnitDevelopmentRiderFlag text, SecondHomeRiderFlag text, OneToFourFamilyRiderFlag text, ConcurrentMtgeDocOrBkPg text, LoanNumber text, MERSMINNumber text, CaseNumber text, MERSFlag text, TitleCompanyName text, TitleCompanyIDStndCode text, AccommodationRecordingFlag text, UnpaidBalance float, InstallmentAmount float, InstallmentDueDate text, TotalDelinquentAmount float, DelinquentAsOfDate text, CurrentLender text, CurrentLenderTypeStndCode text, CurrentLenderIDStndCode text, TrusteeSaleNumber text, AttorneyFileNumber text, AuctionDate text, AuctionTime text, AuctionFullStreetAddress text, AuctionCityName text, StartingBid float, KeyedDate text, KeyerID text, SubVendorStndCode text, ImageFileName text,
      BuilderFlag text, MatchStndCode text, REOStndCode text, UpdateOwnershipFlag text, LoadID integer, StatusInd integer, TransactionTypeStndCode text, BatchID integer, BKFSPID integer, ZVendorStndCode text, SourceChkSum integer, fme_id integer
ForeclosureOriginalLoan (reader CSV2_10)
    attributes: TransId string, FCOrigLoanSequenceNumber string, FCOrigLoanRecordingDate string, FCOrigLoanDocumentDate string, FCOrigLoanDocumentNumber string, FCOrigLoanBookNumber string, FCOrigLoanPageNumber string, FCOrigLender string, FCOrigLenderTypeStndCode string, FCOrigLenderIDStndCode string, FCOrigLoanAmount string, LoadID string, FIPS string, BatchID string
    -> Counter_2
Counter_2
    CNT_ATTR = fme_id
    DOMAIN = counter
    SCOPE = Local
    START = 1
    -> cont_ztrans_utforeclosureoriginalloan (writer SQLITE3_1)
    <REJECTED> -> cont_ztrans_utforeclosureoriginalloan (writer SQLITE3_1)
cont_ztrans_utforeclosureoriginalloan (writer SQLITE3_1)
    attributes: TransId integer, FCOrigLoanSequenceNumber integer, FCOrigLoanRecordingDate text, FCOrigLoanDocumentDate text, FCOrigLoanDocumentNumber text, FCOrigLoanBookNumber text, FCOrigLoanPageNumber text, FCOrigLender text, FCOrigLenderTypeStndCode text, FCOrigLenderIDStndCode text, FCOrigLoanAmount float, LoadID integer, FIPS text, BatchID integer, fme_id integer
BuyerMailAddress (reader CSV2_5)
    attributes: TransId string, BuyerMailSequenceNumber string, BuyerMailCareOfName string, BuyerMailHouseNumber string, BuyerMailHouseNumberExt string, BuyerMailStreetPreDirectional string, BuyerMailStreetName string, BuyerMailStreetSuffix string, BuyerMailStreetPostDirectional string, BuyerMailBuildingName string, BuyerMailBuildingNumber string, BuyerMailFullStreetAddress string, BuyerMailCity string, BuyerMailState string, BuyerMailZip string, BuyerMailZip4 string, OriginalBuyerMailFullStreetAddress string, OriginalBuyerMailAddressLastline string, BuyerMailAddressStndCode string, BuyerMailAddressMatchCode string, BuyerMailAddressUnitDesignatorCode string, BuyerMailAddressUnitNumber string, BuyerMailAddressCarrierRoute string, BuyerMailAddressFIPSCode string, BuyerMailAddressLatitude string, BuyerMailAddressLongitude string, BuyerMailAddressCensusTractAndBlock string, BuyerMailAddressConfidenceScore string, BuyerMailAddressCBSACode string, BuyerMailAddressCBSADivisionCode string,
      BuyerMailAddressMatchType string, BuyerMailAddressDPV string, BuyerMailAddressGeocodeQualityCode string, BuyerMailAddressQualityCode string, LoadID string, FIPS string, BatchID string
    -> Counter_6
Counter_6
    CNT_ATTR = fme_id
    DOMAIN = counter
    SCOPE = Local
    START = 1
    -> cont_ztrans_utbuyermailaddress (writer SQLITE3_1)
    <REJECTED> -> cont_ztrans_utbuyermailaddress (writer SQLITE3_1)
cont_ztrans_utbuyermailaddress (writer SQLITE3_1)
    attributes: TransId integer, BuyerMailSequenceNumber integer, BuyerMailCareOfName text, BuyerMailHouseNumber text, BuyerMailHouseNumberExt text, BuyerMailStreetPreDirectional text, BuyerMailStreetName text, BuyerMailStreetSuffix text, BuyerMailStreetPostDirectional text, BuyerMailBuildingName text, BuyerMailBuildingNumber text, BuyerMailFullStreetAddress text, BuyerMailCity text, BuyerMailState text, BuyerMailZip text, BuyerMailZip4 text, OriginalBuyerMailFullStreetAddress text, OriginalBuyerMailAddressLastline text, BuyerMailAddressStndCode text, BuyerMailAddressMatchCode text, BuyerMailAddressUnitDesignatorCode text, BuyerMailAddressUnitNumber text, BuyerMailAddressCarrierRoute text, BuyerMailAddressFIPSCode text, BuyerMailAddressLatitude float, BuyerMailAddressLongitude float, BuyerMailAddressCensusTractAndBlock text, BuyerMailAddressConfidenceScore integer, BuyerMailAddressCBSACode integer, BuyerMailAddressCBSADivisionCode integer,
      BuyerMailAddressMatchType integer, BuyerMailAddressDPV text, BuyerMailAddressGeocodeQualityCode text, BuyerMailAddressQualityCode text, LoadID integer, FIPS text, BatchID integer, fme_id integer
SellerName (reader CSV2_17)
    attributes: TransId string, SellerFirstMiddleName string, SellerLastName string, SellerIndividualFullName string, SellerNonIndividualName string, SellerNameSequenceNumber string, SellerMailSequenceNumber string, LoadID string, FIPS string, BatchID string
    -> Counter_15
Counter_15
    CNT_ATTR = fme_id
    DOMAIN = counter
    SCOPE = Local
    START = 1
    -> cont_ztrans_utsellername (writer SQLITE3_1)
    <REJECTED> -> cont_ztrans_utsellername (writer SQLITE3_1)
cont_ztrans_utsellername (writer SQLITE3_1)
    attributes: TransId integer, SellerFirstMiddleName text, SellerLastName text, SellerIndividualFullName text, SellerNonIndividualName text, SellerNameSequenceNumber integer, SellerMailSequenceNumber integer, LoadID integer, FIPS text, BatchID integer, fme_id integer
SellerMailAddress (reader CSV2_16)
    attributes: TransId string, SellerMailSequenceNumber string, SellerMailAddressStndCode string, SellerMailCareOfName string, SellerMailHouseNumber string, SellerMailHouseNumberExt string, SellerMailStreetPreDirectional string, SellerMailStreetName string, SellerMailStreetSuffix string, SellerMailStreetPostDirectional string, SellerMailBuildingName string, SellerMailBuildingNumber string, SellerMailFullStreetAddress string, SellerMailCity string, SellerMailState string, SellerMailZip string, SellerMailZip4 string, OriginalSellerMailFullStreetAddress string, OriginalSellerMailAddressLastline string, SellerMailAddressMatchCode string, SellerMailAddressUnitDesignatorCode string, SellerMailAddressUnitNumber string, SellerMailAddressCarrierRoute string, SellerMailAddressFIPSCode string, SellerMailAddressLatitude string, SellerMailAddressLongitude string, SellerMailAddressCensusTractAndBlock string, SellerMailAddressConfidenceScore string, SellerMailAddressCBSACode string, SellerMailAddressCBSADivisionCode string,
      SellerMailAddressMatchType string, SellerMailAddressDPV string, SellerMailAddressGeocodeQualityCode string, SellerMailAddressQualityCode string, LoadID string, FIPS string, BatchID string
    -> Counter_12
Counter_12
    CNT_ATTR = fme_id
    DOMAIN = counter
    SCOPE = Local
    START = 1
    -> cont_ztrans_utsellermailaddress (writer SQLITE3_1)
    <REJECTED> -> cont_ztrans_utsellermailaddress (writer SQLITE3_1)
cont_ztrans_utsellermailaddress (writer SQLITE3_1)
    attributes: TransId integer, SellerMailSequenceNumber integer, SellerMailAddressStndCode text, SellerMailCareOfName text, SellerMailHouseNumber text, SellerMailHouseNumberExt text, SellerMailStreetPreDirectional text, SellerMailStreetName text, SellerMailStreetSuffix text, SellerMailStreetPostDirectional text, SellerMailBuildingName text, SellerMailBuildingNumber text, SellerMailFullStreetAddress text, SellerMailCity text, SellerMailState text, SellerMailZip text, SellerMailZip4 text, OriginalSellerMailFullStreetAddress text, OriginalSellerMailAddressLastline text, SellerMailAddressMatchCode text, SellerMailAddressUnitDesignatorCode text, SellerMailAddressUnitNumber text, SellerMailAddressCarrierRoute text, SellerMailAddressFIPSCode text, SellerMailAddressLatitude float, SellerMailAddressLongitude float, SellerMailAddressCensusTractAndBlock text, SellerMailAddressConfidenceScore integer, SellerMailAddressCBSACode integer, SellerMailAddressCBSADivisionCode integer,
      SellerMailAddressMatchType integer, SellerMailAddressDPV text, SellerMailAddressGeocodeQualityCode text, SellerMailAddressQualityCode text, LoadID integer, FIPS text, BatchID integer, fme_id integer
