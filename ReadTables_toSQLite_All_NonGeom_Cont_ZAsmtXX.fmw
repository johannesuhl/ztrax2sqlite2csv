FME workspace ReadTables_toSQLite_All_NonGeom_Cont_ZAsmtXX.fmw

Parameters:
- DestDataset_SQLITE3 = H:\ZTRAX_ALL\SQLITE\XX_ZAsmt_cont_SQLite.db   # SQLite Database
- SourceDataset_CSV2_33 = H:\ZTRAX_ALL\CSV\cont\XX\ZAsmt\AdditionalPropertyAddress.txt   # Source CSV (Comma Separated Value) File(s)
- SourceDataset_CSV2_25 = H:\ZTRAX_ALL\CSV\cont\XX\ZAsmt\BKManagedSpecific.txt   # Source CSV (Comma Separated Value) File(s)
- SourceDataset_CSV2_41 = H:\ZTRAX_ALL\CSV\cont\XX\ZAsmt\Building.txt   # Source CSV (Comma Separated Value) File(s)
- SourceDataset_CSV2_29 = H:\ZTRAX_ALL\CSV\cont\XX\ZAsmt\BuildingAreas.txt   # Source CSV (Comma Separated Value) File(s)
- SourceDataset_CSV2_37 = H:\ZTRAX_ALL\CSV\cont\XX\ZAsmt\CareOfName.txt   # Source CSV (Comma Separated Value) File(s)
- SourceDataset_CSV2_23 = H:\ZTRAX_ALL\CSV\cont\XX\ZAsmt\ExteriorWall.txt   # Source CSV (Comma Separated Value) File(s)
- SourceDataset_CSV2_27 = H:\ZTRAX_ALL\CSV\cont\XX\ZAsmt\ExtraFeature.txt   # Source CSV (Comma Separated Value) File(s)
- SourceDataset_CSV2_31 = H:\ZTRAX_ALL\CSV\cont\XX\ZAsmt\Garage.txt   # Source CSV (Comma Separated Value) File(s)
- SourceDataset_CSV2_35 = H:\ZTRAX_ALL\CSV\cont\XX\ZAsmt\InteriorFlooring.txt   # Source CSV (Comma Separated Value) File(s)
- SourceDataset_CSV2_39 = H:\ZTRAX_ALL\CSV\cont\XX\ZAsmt\InteriorWall.txt   # Source CSV (Comma Separated Value) File(s)
- SourceDataset_CSV2_43 = H:\ZTRAX_ALL\CSV\cont\XX\ZAsmt\LotSiteAppeal.txt   # Source CSV (Comma Separated Value) File(s)
- SourceDataset_CSV2_24 = H:\ZTRAX_ALL\CSV\cont\XX\ZAsmt\MailAddress.txt   # Source CSV (Comma Separated Value) File(s)
- SourceDataset_CSV2_28 = H:\ZTRAX_ALL\CSV\cont\XX\ZAsmt\Name.txt   # Source CSV (Comma Separated Value) File(s)
- SourceDataset_CSV2_26 = H:\ZTRAX_ALL\CSV\cont\XX\ZAsmt\Oby.txt   # Source CSV (Comma Separated Value) File(s)
- SourceDataset_CSV2_30 = H:\ZTRAX_ALL\CSV\cont\XX\ZAsmt\Pool.txt   # Source CSV (Comma Separated Value) File(s)
- SourceDataset_CSV2_32 = H:\ZTRAX_ALL\CSV\cont\XX\ZAsmt\SaleData.txt   # Source CSV (Comma Separated Value) File(s)
- SourceDataset_CSV2_34 = H:\ZTRAX_ALL\CSV\cont\XX\ZAsmt\TaxDistrict.txt   # Source CSV (Comma Separated Value) File(s)
- SourceDataset_CSV2_36 = H:\ZTRAX_ALL\CSV\cont\XX\ZAsmt\TaxExemption.txt   # Source CSV (Comma Separated Value) File(s)
- SourceDataset_CSV2_38 = H:\ZTRAX_ALL\CSV\cont\XX\ZAsmt\TypeConstruction.txt   # Source CSV (Comma Separated Value) File(s)
- SourceDataset_CSV2_40 = H:\ZTRAX_ALL\CSV\cont\XX\ZAsmt\Value.txt   # Source CSV (Comma Separated Value) File(s)
- SourceDataset_CSV2_42 = H:\ZTRAX_ALL\CSV\cont\XX\ZAsmt\VestingCodes.txt   # Source CSV (Comma Separated Value) File(s)
- SourceDataset_CSV2 = H:\ZTRAX_ALL\CSV\cont\XX\ZAsmt\Main.txt   # Source CSV (Comma Separated Value) File(s)

Readers:
- CSV2_1: CSV2 from $(SourceDataset_CSV2_33) in EPSG:4267
- CSV2_2: CSV2 from $(SourceDataset_CSV2_25) in EPSG:4267
- CSV2_3: CSV2 from $(SourceDataset_CSV2_41) in EPSG:4267
- CSV2_4: CSV2 from $(SourceDataset_CSV2_29) in EPSG:4267
- CSV2_5: CSV2 from $(SourceDataset_CSV2_37) in EPSG:4267
- CSV2_6: CSV2 from $(SourceDataset_CSV2_23) in EPSG:4267
- CSV2_7: CSV2 from $(SourceDataset_CSV2_27) in EPSG:4267
- CSV2_8: CSV2 from $(SourceDataset_CSV2_31) in EPSG:4267
- CSV2_9: CSV2 from $(SourceDataset_CSV2_35) in EPSG:4267
- CSV2_10: CSV2 from $(SourceDataset_CSV2_39) in EPSG:4267
- CSV2_11: CSV2 from $(SourceDataset_CSV2_43) in EPSG:4267
- CSV2_12: CSV2 from $(SourceDataset_CSV2_24) in EPSG:4267
- CSV2_13: CSV2 from $(SourceDataset_CSV2_28) in EPSG:4267
- CSV2_14: CSV2 from $(SourceDataset_CSV2_26) in EPSG:4267
- CSV2_15: CSV2 from $(SourceDataset_CSV2_30) in EPSG:4267
- CSV2_16: CSV2 from $(SourceDataset_CSV2_32) in EPSG:4267
- CSV2_17: CSV2 from $(SourceDataset_CSV2_34) in EPSG:4267
- CSV2_18: CSV2 from $(SourceDataset_CSV2_36) in EPSG:4267
- CSV2_19: CSV2 from $(SourceDataset_CSV2_38) in EPSG:4267
- CSV2_20: CSV2 from $(SourceDataset_CSV2_40) in EPSG:4267
- CSV2_21: CSV2 from $(SourceDataset_CSV2_42) in EPSG:4267
- CSV2_22: CSV2 from $(SourceDataset_CSV2)

Writers:
- SQLITE3_1: SQLITE3 to $(DestDataset_SQLITE3)

cont_zasmt_utextrafeature (writer SQLITE3_1)
    attributes: RowID text, BuildingOrImprovementNumber integer, ExtraFeatureSequenceNumber integer, ExtraFeaturesStndCode text, ExtraFeaturesSqFt integer, ExtraFeaturesLinearFt integer, FIPS text, BatchID integer, fme_id integer
cont_zasmt_uttaxexemption (writer SQLITE3_1)
    attributes: RowID text, TaxExemptionStndCode varchar(20), FIPS text, BatchID integer, fme_id integer
cont_zasmt_utmailaddress (writer SQLITE3_1)
    attributes: RowID text, MailAddressTypeStndCode text, MailHouseNumber text, MailHouseNumberExt text, MailStreetPreDirectional text, MailStreetName text, MailStreetSuffix text, MailStreetPostDirectional text, MailBuildingName text, MailBuildingNumber text, MailFullStreetAddress text, MailCity text, MailState text, MailZip text, MailZip4 text, OriginalMailFullStreetAddress text, OriginalMailAddressLastline text, MailCityStateZip text, MailInternationalAddressFlag text, NameTypeStndCode text, MailAddressMatchCode text, MailAddressUnitDesignatorCode text, MailAddressUnitNumber text, MailAddressCarrierRoute text, MailAddressFIPSCode text, MailAddressLatitude float, MailAddressLongitude float, MailAddressCensusTractAndBlock text, MailAddressConfidenceScore integer, MailAddressCBSACode integer,
      MailAddressCBSADivisionCode integer, MailAddressMatchType integer, MailAddressDPV text, MailAddressGeocodeQualityCode text, MailAddressQualityCode text, FIPS text, BatchID integer, fme_id integer
cont_zasmt_utadditionalpropertyaddress (writer SQLITE3_1)
    attributes: RowID text, PropertyAddressSequenceNumber integer, PropertyHouseNumber text, PropertyHouseNumberExt text, PropertyStreetPreDirectional text, PropertyStreetName text, PropertyStreetSuffix text, PropertyStreetPostDirectional text, PropertyBuildingNumber text, PropertyFullStreetAddress text, PropertyCity text, PropertyState text, PropertyZip text, PropertyZip4 text, OriginalPropertyFullStreetAddress text, OriginalPropertyAddressLastline text, PropertyAddressCensusTract text, PropertyAddressMatchcode text, PropertyAddressUnitDesignator text, PropertyAddressUnitNumber text, PropertyAddressCarrierRoute text, PropertyAddressGeoCodeMatchCode text, PropertyAddressLatitude float, PropertyAddressLongitude float, PropertyAddressCensusTractAndBlock text, PropertyAddressConfidenceScore integer, PropertyAddressCBSACode integer, PropertyAddressCBSADivisionCode integer, PropertyAddressMatchType integer, PropertyAddressDPV text,
      PropertyGeocodeQualityCode text, PropertyAddressQualityCode text, FIPS text, BatchID integer, fme_id integer
cont_zasmt_utsaledata (writer SQLITE3_1)
    attributes: RowID text, SaleSeqNum integer, SellerFullName text, BuyerFullName text, RecordingDate text, DocumentDate text, RecordingDocumentNumber text, RecordingBookNumber text, RecordingPageNumber text, DocumentTypeCountyDescription text, DocumentTypeStndCode text, SalesPriceAmount float, SalesPriceAmountStndCode text, FIPS text, BatchID integer, fme_id integer
cont_zasmt_utbuilding (writer SQLITE3_1)
    attributes: RowID text, NoOfUnits integer, OccupancyStatusStndCode text, PropertyCountyLandUseDescription text, PropertyCountyLandUseCode text, PropertyLandUseStndCode text, PropertyStateLandUseDescription text, PropertyStateLandUseCode text, BuildingOrImprovementNumber integer, BuildingClassStndCode text, BuildingQualityStndCode text, BuildingQualityStndCodeOriginal text, BuildingConditionStndCode text, ArchitecturalStyleStndCode text, YearBuilt integer, EffectiveYearBuilt integer, YearRemodeled integer, NoOfStories text, TotalRooms integer, TotalBedrooms integer, TotalKitchens integer, FullBath integer, ThreeQuarterBath float, HalfBath float, QuarterBath float, TotalCalculatedBathCount float, TotalActualBathCount float, BathSourceStndCode text, TotalBathPlumbingFixtures integer, RoofCoverStndCode text,
      RoofStructureTypeStndCode text, HeatingTypeorSystemStndCode text, AirConditioningTypeorSystemStndCode text, FoundationTypeStndCode text, ElevatorStndCode text, FireplaceFlag text, FirePlaceTypeStndCode text, FireplaceNumber integer, WaterStndCode text, SewerStndCode text, MortgageLenderName text, TimeshareStndCode text, Comments text, LoadID integer, StoryTypeStndCode text, FIPS text, BatchID integer, fme_id integer
cont_zasmt_utcareofname (writer SQLITE3_1)
    attributes: RowID text, NameSequenceNumber integer, NameTypeStndCode text, MailCareOfName text, MailCOPatternStndCode text, FIPS text, BatchID integer, fme_id integer
cont_zasmt_uttaxdistrict (writer SQLITE3_1)
    attributes: RowID text, TaxDistrictStndCode text, TaxDistrictName text, TaxDistrictAmount float, FIPS text, BatchID integer, fme_id integer
cont_zasmt_uttypeconstruction (writer SQLITE3_1)
    attributes: RowID text, BuildingOrImprovementNumber integer, TypeConstructionStndCode text, TypeConstructionPercent float, FIPS text, BatchID integer, fme_id integer
cont_zasmt_utinteriorwall (writer SQLITE3_1)
    attributes: RowID text, BuildingOrImprovementNumber integer, InteriorWallStndCode text, InteriorWallPercent float, FIPS text, BatchID integer, fme_id integer
cont_zasmt_utinteriorflooring (writer SQLITE3_1)
    attributes: RowID text, BuildingOrImprovementNumber integer, InteriorFlooringTypeStndCode text, FlooringPercent float, FIPS text, BatchID integer, fme_id integer
cont_zasmt_utoby (writer SQLITE3_1)
    attributes: RowID text, BuildingOrImprovementNumber integer, OBYSequenceNumber integer, OBYStndCode text, OBYAreaSqFt integer, FIPS text, BatchID integer, fme_id integer
cont_zasmt_utexteriorwall (writer SQLITE3_1)
    attributes: RowID text, BuildingOrImprovementNumber integer, ExteriorWallStndCode text, ExteriorWallPercent float, FIPS text, BatchID integer, fme_id integer
cont_zasmt_utbkmanagedspecific (writer SQLITE3_1)
    attributes: RowID text, LotSizeUnit text, LotSizeorArea text, BKFSPID integer, BKFSLoadDate text, FIPS text, BatchID integer, fme_id integer
cont_zasmt_utbuildingareas (writer SQLITE3_1)
    attributes: RowID text, BuildingOrImprovementNumber integer, BuildingAreaSequenceNumber integer, BuildingAreaStndCode text, BuildingAreaSqFt integer, FIPS text, BatchID integer, fme_id integer
cont_zasmt_utpool (writer SQLITE3_1)
    attributes: RowID text, BuildingOrImprovementNumber integer, PoolStndCode text, PoolSize text, FIPS text, BatchID integer, fme_id integer
cont_zasmt_utlotsiteappeal (writer SQLITE3_1)
    attributes: RowID text, LotSiteAppealStndCode text, FIPS text, BatchID integer, fme_id integer
cont_zasmt_utvalue (writer SQLITE3_1)
    attributes: RowID text, LandAssessedValue float, ImprovementAssessedValue float, TotalAssessedValue float, AssessmentYear integer, LandMarketValue float, ImprovementMarketValue float, TotalMarketValue float, MarketValueYear integer, LandAppraisalValue float, ImprovementAppraisalValue float, TotalAppraisalValue float, AppraisalValueYear integer, FIPS text, BatchID integer, fme_id integer
cont_zasmt_utgarage (writer SQLITE3_1)
    attributes: RowID text, BuildingOrImprovementNumber integer, GarageSequenceNumber integer, GarageStndCode text, GarageAreaSqFt integer, GarageNoOfCars integer, FIPS text, BatchID integer, fme_id integer
cont_zasmt_utvestingcodes (writer SQLITE3_1)
    attributes: RowID text, NameSequenceNumber integer, NameTypeStndCode text, OwnerVestingStndCode text, FIPS text, BatchID integer, fme_id integer
cont_zasmt_utname (writer SQLITE3_1)
    attributes: RowID text, Name text, NameETStndCode text, NameDescriptionStndCode text, NameSequenceNumber integer, NameTypeStndCode text, NamePatternStndCode text, NameClassStndCode text, FIPS text, BatchID integer, fme_id integer
cont_zasmt_utmain (writer SQLITE3_1)
    attributes: RowID varchar(255), ImportParcelID integer, FIPS varchar(255), State varchar(255), County varchar(255), ValueCertDate varchar(255), ExtractDate varchar(255), Edition integer, ZVendorStndCode varchar(255), AssessorParcelNumber varchar(255), DupAPN varchar(255), UnformattedAssessorParcelNumber varchar(255), ParcelSequenceNumber integer, AlternateParcelNumber varchar(255), OldParcelNumber varchar(255), ParcelNumberTypeStndCode varchar(255), RecordSourceStndCode varchar(255), RecordTypeStndCode varchar(255), ConfidentialRecordFlag varchar(255), PropertyAddressSourceStndCode varchar(255), PropertyHouseNumber varchar(255), PropertyHouseNumberExt varchar(255), PropertyStreetPreDirectional varchar(255), PropertyStreetName varchar(255), PropertyStreetSuffix varchar(255), PropertyStreetPostDirectional varchar(255), PropertyFullStreetAddress varchar(255), PropertyCity varchar(255), PropertyState varchar(255), PropertyZip varchar(255),
      PropertyZip4 varchar(255), OriginalPropertyFullStreetAddress varchar(255), OriginalPropertyAddressLastline varchar(255), PropertyBuildingNumber varchar(255), PropertyZoningDescription varchar(255), PropertyZoningSourceCode varchar(255), CensusTract varchar(255), TaxIDNumber varchar(255), TaxAmount real(31,15), TaxYear integer, TaxDelinquencyFlag varchar(255), TaxDelinquencyAmount real(31,15), TaxDelinquencyYear integer, TaxRateCodeArea varchar(255), LegalLot varchar(255), LegalLotStndCode varchar(255), LegalOtherLot varchar(255), LegalBlock varchar(255), LegalSubdivisionCode varchar(255), LegalSubdivisionName varchar(255), LegalCondoProjectPUDDevName varchar(255), LegalBuildingNumber varchar(255), LegalUnit varchar(255), LegalSection varchar(255), LegalPhase varchar(255), LegalTract varchar(255), LegalDistrict varchar(255), LegalMunicipality varchar(255), LegalCity varchar(255), LegalTownship varchar(255),
      LegalSTRSection varchar(255), LegalSTRTownship varchar(255), LegalSTRRange varchar(255), LegalSTRMeridian varchar(255), LegalSecTwnRngMer varchar(255), LegalRecordersMapReference varchar(255), LegalDescription varchar(255), LegalNeighborhoodSourceCode varchar(255), NoOfBuildings integer, LotSizeAcres real(31,15), LotSizeSquareFeet real(31,15), LotSizeFrontageFeet real(31,15), LotSizeDepthFeet real(31,15), LotSizeIRR varchar(255), LotSiteTopographyStndCode varchar(255), LoadID integer, PropertyAddressMatchcode varchar(255), PropertyAddressUnitDesignator varchar(255), PropertyAddressUnitNumber varchar(255), PropertyAddressCarrierRoute varchar(255), PropertyAddressGeoCodeMatchCode varchar(255), PropertyAddressLatitude real(31,15), PropertyAddressLongitude real(31,15), PropertyAddressCensusTractAndBlock varchar(255), PropertyAddressConfidenceScore integer, PropertyAddressCBSACode integer, PropertyAddressCBSADivisionCode integer, PropertyAddressMatchType integer, PropertyAddressDPV varchar(255), PropertyGeocodeQualityCode varchar(255),
      PropertyAddressQualityCode varchar(255), SubEdition integer, BatchID integer, BKFSPID integer, SourceChkSum integer, fme_id integer

Bookmark: cont_zasmt
ExtraFeature (reader CSV2_7)
    attributes: RowID string, BuildingOrImprovementNumber string, ExtraFeatureSequenceNumber string, ExtraFeaturesStndCode string, ExtraFeaturesSqFt string, ExtraFeaturesLinearFt string, FIPS string, BatchID string
    -> Counter_14
Counter_14
    CNT_ATTR = fme_id
    DOMAIN = counter
    SCOPE = Local
    START = 1
    -> cont_zasmt_utextrafeature (writer SQLITE3_1)
    <REJECTED> -> cont_zasmt_utextrafeature (writer SQLITE3_1)
TaxExemption (reader CSV2_18)
    attributes: RowID string, TaxExemptionStndCode string, FIPS string, BatchID string
    -> Counter_3
Counter_3
    CNT_ATTR = fme_id
    DOMAIN = counter
    SCOPE = Local
    START = 1
    -> cont_zasmt_uttaxexemption (writer SQLITE3_1)
    <REJECTED> -> cont_zasmt_uttaxexemption (writer SQLITE3_1)
MailAddress (reader CSV2_12)
    attributes: RowID string, MailAddressTypeStndCode string, MailHouseNumber string, MailHouseNumberExt string, MailStreetPreDirectional string, MailStreetName string, MailStreetSuffix string, MailStreetPostDirectional string, MailBuildingName string, MailBuildingNumber string, MailFullStreetAddress string, MailCity string, MailState string, MailZip string, MailZip4 string, OriginalMailFullStreetAddress string, OriginalMailAddressLastline string, MailCityStateZip string, MailInternationalAddressFlag string, NameTypeStndCode string, MailAddressMatchCode string, MailAddressUnitDesignatorCode string, MailAddressUnitNumber string, MailAddressCarrierRoute string, MailAddressFIPSCode string, MailAddressLatitude string, MailAddressLongitude string, MailAddressCensusTractAndBlock string, MailAddressConfidenceScore string, MailAddressCBSACode string,
      MailAddressCBSADivisionCode string, MailAddressMatchType string, MailAddressDPV string, MailAddressGeocodeQualityCode string, MailAddressQualityCode string, FIPS string, BatchID string
    -> Counter_4
Counter_4
    CNT_ATTR = fme_id
    DOMAIN = counter
    SCOPE = Local
    START = 1
    -> cont_zasmt_utmailaddress (writer SQLITE3_1)
    <REJECTED> -> cont_zasmt_utmailaddress (writer SQLITE3_1)
AdditionalPropertyAddress (reader CSV2_1)
    attributes: RowID string, PropertyAddressSequenceNumber string, PropertyHouseNumber string, PropertyHouseNumberExt string, PropertyStreetPreDirectional string, PropertyStreetName string, PropertyStreetSuffix string, PropertyStreetPostDirectional string, PropertyBuildingNumber string, PropertyFullStreetAddress string, PropertyCity string, PropertyState string, PropertyZip string, PropertyZip4 string, OriginalPropertyFullStreetAddress string, OriginalPropertyAddressLastline string, PropertyAddressCensusTract string, PropertyAddressMatchcode string, PropertyAddressUnitDesignator string, PropertyAddressUnitNumber string, PropertyAddressCarrierRoute string, PropertyAddressGeoCodeMatchCode string, PropertyAddressLatitude string, PropertyAddressLongitude string, PropertyAddressCensusTractAndBlock string, PropertyAddressConfidenceScore string, PropertyAddressCBSACode string, PropertyAddressCBSADivisionCode string, PropertyAddressMatchType string, PropertyAddressDPV string,
      PropertyGeocodeQualityCode string, PropertyAddressQualityCode string, FIPS string, BatchID string
    -> Counter_21
Counter_21
    CNT_ATTR = fme_id
    DOMAIN = counter
    SCOPE = Local
    START = 1
    -> cont_zasmt_utadditionalpropertyaddress (writer SQLITE3_1)
    <REJECTED> -> cont_zasmt_utadditionalpropertyaddress (writer SQLITE3_1)
SaleData (reader CSV2_16)
    attributes: RowID string, SaleSeqNum string, SellerFullName string, BuyerFullName string, RecordingDate string, DocumentDate string, RecordingDocumentNumber string, RecordingBookNumber string, RecordingPageNumber string, DocumentTypeCountyDescription string, DocumentTypeStndCode string, SalesPriceAmount string, SalesPriceAmountStndCode string, FIPS string, BatchID string
    -> Counter_5
Counter_5
    CNT_ATTR = fme_id
    DOMAIN = counter
    SCOPE = Local
    START = 1
    -> cont_zasmt_utsaledata (writer SQLITE3_1)
    <REJECTED> -> cont_zasmt_utsaledata (writer SQLITE3_1)
Building (reader CSV2_3)
    attributes: RowID string, NoOfUnits string, OccupancyStatusStndCode string, PropertyCountyLandUseDescription string, PropertyCountyLandUseCode string, PropertyLandUseStndCode string, PropertyStateLandUseDescription string, PropertyStateLandUseCode string, BuildingOrImprovementNumber string, BuildingClassStndCode string, BuildingQualityStndCode string, BuildingQualityStndCodeOriginal string, BuildingConditionStndCode string, ArchitecturalStyleStndCode string, YearBuilt string, EffectiveYearBuilt string, YearRemodeled string, NoOfStories string, TotalRooms string, TotalBedrooms string, TotalKitchens string, FullBath string, ThreeQuarterBath string, HalfBath string, QuarterBath string, TotalCalculatedBathCount string, TotalActualBathCount string, BathSourceStndCode string, TotalBathPlumbingFixtures string, RoofCoverStndCode string,
      RoofStructureTypeStndCode string, HeatingTypeorSystemStndCode string, AirConditioningTypeorSystemStndCode string, FoundationTypeStndCode string, ElevatorStndCode string, FireplaceFlag string, FirePlaceTypeStndCode string, FireplaceNumber string, WaterStndCode string, SewerStndCode string, MortgageLenderName string, TimeshareStndCode string, Comments string, LoadID string, StoryTypeStndCode string, FIPS string, BatchID string
    -> Counter_8
Counter_8
    CNT_ATTR = fme_id
    DOMAIN = counter
    SCOPE = Local
    START = 1
    -> cont_zasmt_utbuilding (writer SQLITE3_1)
    <REJECTED> -> cont_zasmt_utbuilding (writer SQLITE3_1)
CareOfName (reader CSV2_5)
    attributes: RowID string, NameSequenceNumber string, NameTypeStndCode string, MailCareOfName string, MailCOPatternStndCode string, FIPS string, BatchID string
    -> Counter_11
Counter_11
    CNT_ATTR = fme_id
    DOMAIN = counter
    SCOPE = Local
    START = 1
    -> cont_zasmt_utcareofname (writer SQLITE3_1)
    <REJECTED> -> cont_zasmt_utcareofname (writer SQLITE3_1)
TaxDistrict (reader CSV2_17)
    attributes: RowID string, TaxDistrictStndCode string, TaxDistrictName string, TaxDistrictAmount string, FIPS string, BatchID string
    -> Counter_15
Counter_15
    CNT_ATTR = fme_id
    DOMAIN = counter
    SCOPE = Local
    START = 1
    -> cont_zasmt_uttaxdistrict (writer SQLITE3_1)
    <REJECTED> -> cont_zasmt_uttaxdistrict (writer SQLITE3_1)
TypeConstruction (reader CSV2_19)
    attributes: RowID string, BuildingOrImprovementNumber string, TypeConstructionStndCode string, TypeConstructionPercent string, FIPS string, BatchID string
    -> Counter_10
Counter_10
    CNT_ATTR = fme_id
    DOMAIN = counter
    SCOPE = Local
    START = 1
    -> cont_zasmt_uttypeconstruction (writer SQLITE3_1)
    <REJECTED> -> cont_zasmt_uttypeconstruction (writer SQLITE3_1)
InteriorWall (reader CSV2_10)
    attributes: RowID string, BuildingOrImprovementNumber string, InteriorWallStndCode string, InteriorWallPercent string, FIPS string, BatchID string
    -> Counter_20
Counter_20
    CNT_ATTR = fme_id
    DOMAIN = counter
    SCOPE = Local
    START = 1
    -> cont_zasmt_utinteriorwall (writer SQLITE3_1)
    <REJECTED> -> cont_zasmt_utinteriorwall (writer SQLITE3_1)
InteriorFlooring (reader CSV2_9)
    attributes: RowID string, BuildingOrImprovementNumber string, InteriorFlooringTypeStndCode string, FlooringPercent string, FIPS string, BatchID string
    -> Counter_12
Counter_12
    CNT_ATTR = fme_id
    DOMAIN = counter
    SCOPE = Local
    START = 1
    -> cont_zasmt_utinteriorflooring (writer SQLITE3_1)
    <REJECTED> -> cont_zasmt_utinteriorflooring (writer SQLITE3_1)
Oby (reader CSV2_14)
    attributes: RowID string, BuildingOrImprovementNumber string, OBYSequenceNumber string, OBYStndCode string, OBYAreaSqFt string, FIPS string, BatchID string
    -> Counter_9
Counter_9
    CNT_ATTR = fme_id
    DOMAIN = counter
    SCOPE = Local
    START = 1
    -> cont_zasmt_utoby (writer SQLITE3_1)
    <REJECTED> -> cont_zasmt_utoby (writer SQLITE3_1)
ExteriorWall (reader CSV2_6)
    attributes: RowID string, BuildingOrImprovementNumber string, ExteriorWallStndCode string, ExteriorWallPercent string, FIPS string, BatchID string
    -> Counter_19
Counter_19
    CNT_ATTR = fme_id
    DOMAIN = counter
    SCOPE = Local
    START = 1
    -> cont_zasmt_utexteriorwall (writer SQLITE3_1)
    <REJECTED> -> cont_zasmt_utexteriorwall (writer SQLITE3_1)
BKManagedSpecific (reader CSV2_2)
    attributes: RowID string, LotSizeUnit string, LotSizeorArea string, BKFSPID string, BKFSLoadDate string, FIPS string, BatchID string
    -> Counter_7
Counter_7
    CNT_ATTR = fme_id
    DOMAIN = counter
    SCOPE = Local
    START = 1
    -> cont_zasmt_utbkmanagedspecific (writer SQLITE3_1)
    <REJECTED> -> cont_zasmt_utbkmanagedspecific (writer SQLITE3_1)
BuildingAreas (reader CSV2_4)
    attributes: RowID string, BuildingOrImprovementNumber string, BuildingAreaSequenceNumber string, BuildingAreaStndCode string, BuildingAreaSqFt string, FIPS string, BatchID string
    -> Counter_6
Counter_6
    CNT_ATTR = fme_id
    DOMAIN = counter
    SCOPE = Local
    START = 1
    -> cont_zasmt_utbuildingareas (writer SQLITE3_1)
    <REJECTED> -> cont_zasmt_utbuildingareas (writer SQLITE3_1)
Pool (reader CSV2_15)
    attributes: RowID string, BuildingOrImprovementNumber string, PoolStndCode string, PoolSize string, FIPS string, BatchID string
    -> Counter_22
Counter_22
    CNT_ATTR = fme_id
    DOMAIN = counter
    SCOPE = Local
    START = 1
    -> cont_zasmt_utpool (writer SQLITE3_1)
    <REJECTED> -> cont_zasmt_utpool (writer SQLITE3_1)
LotSiteAppeal (reader CSV2_11)
    attributes: RowID string, LotSiteAppealStndCode string, FIPS string, BatchID string
    -> Counter_18
Counter_18
    CNT_ATTR = fme_id
    DOMAIN = counter
    SCOPE = Local
    START = 1
    -> cont_zasmt_utlotsiteappeal (writer SQLITE3_1)
    <REJECTED> -> cont_zasmt_utlotsiteappeal (writer SQLITE3_1)
Value (reader CSV2_20)
    attributes: RowID string, LandAssessedValue string, ImprovementAssessedValue string, TotalAssessedValue string, AssessmentYear string, LandMarketValue string, ImprovementMarketValue string, TotalMarketValue string, MarketValueYear string, LandAppraisalValue string, ImprovementAppraisalValue string, TotalAppraisalValue string, AppraisalValueYear string, FIPS string, BatchID string
    -> Counter_13
Counter_13
    CNT_ATTR = fme_id
    DOMAIN = counter
    SCOPE = Local
    START = 1
    -> cont_zasmt_utvalue (writer SQLITE3_1)
    <REJECTED> -> cont_zasmt_utvalue (writer SQLITE3_1)
Garage (reader CSV2_8)
    attributes: RowID string, BuildingOrImprovementNumber string, GarageSequenceNumber string, GarageStndCode string, GarageAreaSqFt string, GarageNoOfCars string, FIPS string, BatchID string
    -> Counter_17
Counter_17
    CNT_ATTR = fme_id
    DOMAIN = counter
    SCOPE = Local
    START = 1
    -> cont_zasmt_utgarage (writer SQLITE3_1)
    <REJECTED> -> cont_zasmt_utgarage (writer SQLITE3_1)
VestingCodes (reader CSV2_21)
    attributes: RowID string, NameSequenceNumber string, NameTypeStndCode string, OwnerVestingStndCode string, FIPS string, BatchID string
    -> Counter_16
Counter_16
    CNT_ATTR = fme_id
    DOMAIN = counter
    SCOPE = Local
    START = 1
    -> cont_zasmt_utvestingcodes (writer SQLITE3_1)
    <REJECTED> -> cont_zasmt_utvestingcodes (writer SQLITE3_1)
Name (reader CSV2_13)
    attributes: RowID string, Name string, NameETStndCode string, NameDescriptionStndCode string, NameSequenceNumber string, NameTypeStndCode string, NamePatternStndCode string, NameClassStndCode string, FIPS string, BatchID string
    -> Counter_2
Counter_2
    CNT_ATTR = fme_id
    DOMAIN = counter
    SCOPE = Local
    START = 1
    -> cont_zasmt_utname (writer SQLITE3_1)
    <REJECTED> -> cont_zasmt_utname (writer SQLITE3_1)
Main (reader CSV2_22)
    attributes: RowID string, ImportParcelID string, FIPS string, State string, County string, ValueCertDate string, ExtractDate string, Edition string, ZVendorStndCode string, AssessorParcelNumber string, DupAPN string, UnformattedAssessorParcelNumber string, ParcelSequenceNumber string, AlternateParcelNumber string, OldParcelNumber string, ParcelNumberTypeStndCode string, RecordSourceStndCode string, RecordTypeStndCode string, ConfidentialRecordFlag string, PropertyAddressSourceStndCode string, PropertyHouseNumber string, PropertyHouseNumberExt string, PropertyStreetPreDirectional string, PropertyStreetName string, PropertyStreetSuffix string, PropertyStreetPostDirectional string, PropertyFullStreetAddress string, PropertyCity string, PropertyState string, PropertyZip string,
      PropertyZip4 string, OriginalPropertyFullStreetAddress string, OriginalPropertyAddressLastline string, PropertyBuildingNumber string, PropertyZoningDescription string, PropertyZoningSourceCode string, CensusTract string, TaxIDNumber string, TaxAmount string, TaxYear string, TaxDelinquencyFlag string, TaxDelinquencyAmount string, TaxDelinquencyYear string, TaxRateCodeArea string, LegalLot string, LegalLotStndCode string, LegalOtherLot string, LegalBlock string, LegalSubdivisionCode string, LegalSubdivisionName string, LegalCondoProjectPUDDevName string, LegalBuildingNumber string, LegalUnit string, LegalSection string, LegalPhase string, LegalTract string, LegalDistrict string, LegalMunicipality string, LegalCity string, LegalTownship string,
      LegalSTRSection string, LegalSTRTownship string, LegalSTRRange string, LegalSTRMeridian string, LegalSecTwnRngMer string, LegalRecordersMapReference string, LegalDescription string, LegalNeighborhoodSourceCode string, NoOfBuildings string, LotSizeAcres string, LotSizeSquareFeet string, LotSizeFrontageFeet string, LotSizeDepthFeet string, LotSizeIRR string, LotSiteTopographyStndCode string, LoadID string, PropertyAddressMatchcode string, PropertyAddressUnitDesignator string, PropertyAddressUnitNumber string, PropertyAddressCarrierRoute string, PropertyAddressGeoCodeMatchCode string, PropertyAddressLatitude string, PropertyAddressLongitude string, PropertyAddressCensusTractAndBlock string, PropertyAddressConfidenceScore string, PropertyAddressCBSACode string, PropertyAddressCBSADivisionCode string, PropertyAddressMatchType string, PropertyAddressDPV string, PropertyGeocodeQualityCode string,
      PropertyAddressQualityCode string, SubEdition string, BatchID string, BKFSPID string, SourceChkSum string
    -> Counter_23
Counter_23
    CNT_ATTR = fme_id
    DOMAIN = counter
    SCOPE = Local
    START = 1
    -> cont_zasmt_utmain (writer SQLITE3_1)
    <REJECTED> -> cont_zasmt_utmain (writer SQLITE3_1)
